FME workspace clip_roads.fmw

Parameters:
- inroads = F:\URBAN_SCALING_ROADNETWORKS_USC\temp\tempdata.gdb   # File Geodatabase
- inareas = F:\URBAN_SCALING_ROADNETWORKS_USC\outdata_spatial\segments_selected.shp
- outfolder = F:\URBAN_SCALING_ROADNETWORKS_USC\outdata_roads   # Destination Esri Shapefile Folder
- artific_deadends_points = roads_10100_1000_005_1900artific_deadends
- outroads = roads_10100_1000_005_1900

Readers:
- FILEGDB_1: FILEGDB from $(inroads)
- ESRISHAPE_1: ESRISHAPE from $(inareas)

Writers:
- ESRISHAPE_2: ESRISHAPE to $(outfolder)
- ESRISHAPE_3: ESRISHAPE to $(outfolder)

counties_merged (reader FILEGDB_1)
    attributes: OBJECTID objectid, MTFCC_CODE text(50), SHAPE_Length double
    -> Clipper_3 [CLIPPEE]
segments_selected (reader ESRISHAPE_1)
    attributes: Id long, gridcode long, area double
    -> GeometryCoercer_2
    -> Clipper_3 [CLIPPER]
    -> LineOnAreaOverlayer [AREA]
GeometryCoercer_2
    GQUERY:
      for $geom in //geometry
      where $geom/count(parent::geometry) = 0
      return number($geom/@fme_id)
    KIND = fme_line
    COERCED -> Bufferer_2
Bufferer_2
    ANGLE = 22.5
    CAP_STYLE = Round
    CORNER_STYLE = Round
    OFFSET = 0.00001
    BUFFERED -> PointOnAreaOverlayer_3 [AREA]
Clipper_3
    ATTR_ACCUM_MODE = Merge Clipper
    ATTR_CONFLICT_RES = Use Clippee
    BOUNDARY_CASES = Treat as Inside
    CLEANING_TOLERANCE = Automatic
    CLIPPED_ATTR = _clipped
    CLIP_TYPE = Multiple Clippers
    CONNECT_Z_MODE = First Wins
    LINES_AS_SEGMENTS = No
    MEASURE_TYPE = Continuous
    MISSING_VAL_MODE = Compute
    PRESERVE_CLIPPEE_EXTENTS = No
    VAL_SOURCE = Clippee Only
    INSIDE -> TopologyBuilder_2
    INSIDE -> LineOnAreaOverlayer [LINE]
TopologyBuilder_2
    ALLOW_CYCLES = No
    BOUNDING_EDGES = All
    CLEAN_DATA = No
    DEAGGREGATE_INPUT = Yes
    MAX = 100
    OVERLAPPING_MODE = No
    PROP_ATTRS = Yes
    NODE -> PointOnAreaOverlayer_3 [POINT]
PointOnAreaOverlayer_3
    ATTR_ACCUM_MODE = Merge Incoming
    ATTR_CONFLICT_RES = Use Original
    DEAGGREGATE_INPUT = Yes
    OV_ATTR = _overlaps_wClipLineBuffer
    POLYS_FIRST = NO
    POINT -> Tester_3
Tester_3
    BOOL_OP = OR
    COMPOSITE_TEST = 1
    TEST_CLAUSE = TEST @Value(_overlaps_wClipLineBuffer) > 0
    TEST_MODE = TEST
    PASSED -> artific_deadend_nodes (writer ESRISHAPE_3)
artific_deadend_nodes (writer ESRISHAPE_3)
    attributes: OBJECTID long
LineOnAreaOverlayer
    ATTR_ACCUM_MODE = Merge Incoming
    ATTR_CONFLICT_RES = Use Original
    CLEANING_TOLERANCE = Automatic
    DEAGGREGATE_INPUT = Yes
    OV_ATTR = _overlaps
    LINE -> road_netw (writer ESRISHAPE_2)
road_netw (writer ESRISHAPE_2)
    attributes: OBJECTID long, MTFCC_CODE char(50), Id long

FME custom transformer LoopFilter_2
Tests whether a line is a loop, i.e. whether its end matches the beginning.
The transformers outputs loops through PASSED port, and non-loops through FAILED port.
An isLoop attribute is added to each feature. 1 means the feature is loop, and zero means it is not.

LINE (input)
    -> LineFilter
Note: LoopFilter / Dmitri Bagh / July 11, 2005
LineFilter: GeometryFilter
    POINT -> NON-LINEAR (output)
    LINE -> LoopTester
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    EXPRESSION = (@Coordinate(x,0)-@Coordinate(x,-1))||(@Coordinate(y,0)-@Coordinate(y,-1))
    VAL_ATTR = _isLoop
    -> TESTER
Note: TESTER [Tester:1] / Test Description: <not set> / TEST &_isLoop = 0 / Condition: OR / Composite Test Expression: <not set> / Version: 1
TESTER: Tester
    BOOL_OP = OR
    TEST_CLAUSE = TEST &_isLoop = 0
    TEST_MODE = Automatic
    PASSED -> PASSED (output)
    FAILED -> FAILED (output)
PASSED (output)
FAILED (output)
NON-LINEAR (output)
