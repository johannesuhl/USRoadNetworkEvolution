FME workspace clip_roads_to_hist_settlements.fmw

Parameters:
- SourceDataset_GEOTIFF = $(FME_MF_DIR)00_FBUY_COMPOSITE_semidecadal.tif   # Source GeoTIFF File(s)
- state = 42
- SourceDataset_FILEGDB = H:\NAT_TRANSP_DATA\TRAN_42_Pennsylvania_GU_STATEORTERRITORY\TRAN_42_Pennsylvania_GU_STATEORTERRITORY.gdb   # File Geodatabase
- county = 42133
- SourceDataset_ESRISHAPE = $(FME_MF_DIR)us_county_2015_5m_lower48.shp   # Source Esri Shapefile(s)
- year_start = 1
- year_end = 1925
- DestDataset_CSV2 = H:\NAT_TRANSP_DATA\OUTPUTS   # Destination CSV (Comma Separated Value) Folder

Readers:
- GEOTIFF_1: GEOTIFF from $(SourceDataset_GEOTIFF)
- FILEGDB_1: FILEGDB from $(SourceDataset_FILEGDB) in EPSG:4269
- ESRISHAPE_1: ESRISHAPE from $(SourceDataset_ESRISHAPE)

Writers:
- CSV2_1: CSV2 to $(DestDataset_CSV2)

Transportation/Trans_RoadSegment (reader FILEGDB_1)
    attributes: OBJECTID objectid, PERMANENT_IDENTIFIER text(40), SOURCE_FEATUREID text(40), SOURCE_DATASETID text(40), SOURCE_DATADESC text(100), SOURCE_ORIGINATOR text(130), LOADDATE date, INTERSTATE text(25), INTERSTATE_A text(25), INTERSTATE_B text(25), INTERSTATE_C text(25), US_ROUTE text(25), US_ROUTE_A text(25), US_ROUTE_B text(25), US_ROUTE_C text(25), STATE_ROUTE text(25), STATE_ROUTE_A text(25), STATE_ROUTE_B text(25), STATE_ROUTE_C text(25), COUNTY_ROUTE text(25), FEDERAL_LANDS_ROUTE text(25), STCO_FIPSCODE text(5), TNMFRC text(42), FULL_STREET_NAME text(100), MTFCC_CODE text(50), SHAPE_Length double
    -> EsriReprojector_3
    -> Transportation_Trans_RoadSegment
EsriReprojector_3
    DEST = ESRIWKT|USA_Contiguous_Albers_Equal_Area_Conic_USGS_version|PROJCS["USA_Contiguous_Albers_Equal_Area_Conic_USGS_version",GEOGCS["GCS_North_American_1983",DATUM["D_North_American_1983",SPHEROID["GRS_1980",6378137.0,298.257222101]],PRIMEM["Greenwich",0.0],UNIT["Degree",0.0174532925199433]],PROJECTION["Albers"],PARAMETER["False_Easting",0.0],PARAMETER["False_Northing",0.0],PARAMETER["Central_Meridian",-96.0],PARAMETER["Standard_Parallel_1",29.5],PARAMETER["Standard_Parallel_2",45.5],PARAMETER["Latitude_Of_Origin",23.0],UNIT["Meter",1.0]]
    RASTER_CELL_SIZE = Preserve Cells
    SOURCE = ESRIWKT|GCS_North_American_1983|GEOGCS["GCS_North_American_1983",DATUM["D_North_American_1983",SPHEROID["GRS_1980",6378137.0,298.257222101]],PRIMEM["Greenwich",0.0],UNIT["Degree",0.0174532925199433]]
    GEOTRANSFORMATION_DIRECTION = Forward
    INTERPOLATION_TYPE_NAME = Nearest Neighbor
    REPROJECTED -> Clipper_2 [CLIPPEE]
Transportation_Trans_RoadSegment: Inspector [off]
us_county_2015_5m_lower48 (reader ESRISHAPE_1)
    attributes: STATEFP char(2), COUNTYFP char(3), COUNTYNS char(8), AFFGEOID char(14), GEOID char(5), NAME char(100), LSAD char(2), ALAND number(14,0), AWATER number(14,0)
    -> Tester_5
Tester_5
    TEST_CLAUSE = STRING_TEST @Value(GEOID) CONTAINS $(county)
    BOOL_OP = OR
    TEST_DESCRIPTION = ""
    TEST_MODE = Automatic
    PASSED -> Clipper [CLIPPER]
GEOTIFF (reader GEOTIFF_1)
    attributes: datatype char(255)
    -> Clipper [CLIPPEE]
Clipper
    PRESERVE_CLIPPEE_EXTENTS = No
    CLIP_TYPE = Multiple Clippers
    BOUNDARY_CASES = Treat as Inside
    ATTR_ACCUM_MODE = Merge Clipper
    LINES_AS_SEGMENTS = No
    DEFAULT_VAL = 0
    CLIPPED_ATTR = _clipped
    VAL_SOURCE = Clippee Only
    MEASURE_TYPE = Continuous
    CONNECT_Z_MODE = First Wins
    MISSING_VAL_MODE = Compute
    CREATE_AGGREGATES = Yes
    ATTR_CONFLICT_RES = Use Clippee
    INSIDE -> RasterCellCoercer
RasterCellCoercer
    EXTRACT_NODATA = No
    EXTRACT_BAND_VALUES_AS = Attributes
    CELL_GEOMETRY = Polygons
    PRESERVE_ATTRIBUTES = No
    -> Tester
Tester
    TEST_CLAUSE:
      TEST @Value(_band{0}.value) <= $(year_end)
      TEST @Value(_band{0}.value) > $(year_start)
    BOOL_OP = AND
    TEST_DESCRIPTION = ""
    TEST_MODE = Automatic
    PASSED -> Tester_Passed
    PASSED -> Aggregator
Aggregator
    AGGREGATE_TYPE = Heterogeneous Collection
    ORDERED = No
    ACCUM_ATTRS_NAME = Use Attributes From One Feature
    SEP = ,
    MODE = Geometry - Assemble One Level
    AGGREGATE -> Dissolver
Dissolver
    ACCUM_INPUT_ATTRS = Use Attributes From One Feature
    NO_OVRLP = No
    DEAGGREGATE_INPUT = Yes
    CONNECT_Z_MODE = First Wins
    AREA -> Counter
Counter
    START = 0
    DOMAIN = counter
    CNT_ATTR = bu_patch_id
    SCOPE = Global
    -> AreaCalculator
Note: area of grid cells in time slice for area calc
AreaCalculator
    AREA_TYPE = Plane Area
    AREA_ATTR = BU_AREA_BUF
    MULT = 1
    -> CenterPointExtractor
    -> AreaCalculator_Output
    <REJECTED> -> AreaCalculator__Rejected_
AreaCalculator_Output: Inspector [off]
AreaCalculator__Rejected_: Inspector [off]
CenterPointExtractor
    MODE = Inside
    CENTY = centr_y
    CENTX = centr_x
    CENTZ = centr_z
    -> BoundingBoxReplacer
    -> FeatureMerger [REQUESTOR]
BoundingBoxReplacer
    BOXTYPE = Oriented Bounding Box
    BBLONGER = orient_bb_b
    BBSHORTER = orient_bb_a
    BOX -> AttributeKeeper
AttributeKeeper
    KEEP_ATTRS = orient_bb_a,bu_patch_id,orient_bb_b
    -> FeatureMerger [SUPPLIER]
FeatureMerger
    SUPPLIERS_FIRST = No
    ATTR_ACCUM_MODE = Merge Supplier
    IGNORE_NULLS = No
    MERGE_TYPE = Attributes Only
    PROCESS_DUPS = No
    REJECT_NULL_MISSING_KEYS = No
    JOIN_KEYS = @Value(bu_patch_id) @Value(bu_patch_id) AUTO
    ATTR_CONFLICT_RES = Use Requestor
    MERGED -> GeometryCoercer
    MERGED -> PointOnAreaOverlayer [AREA]
    MERGED -> Clipper_2 [CLIPPER]
GeometryCoercer
    GQUERY:
      for $geom in //geometry
      where $geom/count(parent::geometry) = 0
      return number($geom/@fme_id)
    KIND = fme_line
    COERCED -> Bufferer
Bufferer
    CORNER_STYLE = Round
    OFFSET = 1
    CAP_STYLE = Round
    ANGLE = 22.5
    BUFFERED -> PointOnAreaOverlayer_2 [AREA]
Clipper_2
    PRESERVE_CLIPPEE_EXTENTS = No
    CLIP_TYPE = Multiple Clippers
    BOUNDARY_CASES = Treat as Inside
    ATTR_ACCUM_MODE = Merge Clipper
    LINES_AS_SEGMENTS = No
    CLIPPED_ATTR = _clipped
    VAL_SOURCE = Clippee Only
    MEASURE_TYPE = Continuous
    MISSING_VAL_MODE = Compute
    CREATE_AGGREGATES = Yes
    ATTR_CONFLICT_RES = Use Clippee
    INSIDE -> Clipper_2_Inside
    INSIDE -> LengthCalculator
    INSIDE -> Chopper_2
Clipper_2_Inside: Inspector [off]
LengthCalculator
    LEN_ATTR = _length_orig
    MULT = 1
    DIM = 2
    -> TopologyBuilder
TopologyBuilder
    DEAGGREGATE_INPUT = Yes
    MAX = 100
    ALLOW_CYCLES = No
    OVERLAPPING_MODE = No
    PROP_ATTRS = Yes
    CLEAN_DATA = No
    BOUNDING_EDGES = All
    NODE -> PointOnAreaOverlayer_2 [POINT]
    LINE -> TopologyBuilder_Edge
    LINE -> LengthCalculator_2
PointOnAreaOverlayer_2
    POLYS_FIRST = NO
    OV_ATTR = _overlaps_wClipLineBuffer
    ATTR_ACCUM_MODE = Merge Incoming
    DEAGGREGATE_INPUT = Yes
    ATTR_CONFLICT_RES = Use Original
    POINT -> Tester_2
Tester_2
    TEST_CLAUSE = TEST @Value(_overlaps_wClipLineBuffer) = 0
    BOOL_OP = OR
    TEST_DESCRIPTION = ""
    TEST_MODE = Automatic
    PASSED -> PointOnAreaOverlayer [POINT]
PointOnAreaOverlayer
    POLYS_FIRST = No
    CANDIDATE_LIST_ATTRS_TO_INCLUDE_MODE = Selected Attributes
    OV_ATTR = _overlaps
    ATTR_ACCUM_MODE = Merge Incoming
    DEAGGREGATE_INPUT = Yes
    ATTR_CONFLICT_RES = Use Original
    POINT -> File1 (writer CSV2_1)
Note: gives us number of nodes (intersections and dead ends based on number of reported angles)
File1 (writer CSV2_1)
    attributes: BU_AREA_BUF real32, OBJECTID string, PERMANENT_IDENTIFIER string, STCO_FIPSCODE string, _node_angle_0_.fme_arc_angle real32, _node_angle_1_.fme_arc_angle real32, _node_angle_2_.fme_arc_angle real32, _node_angle_3_.fme_arc_angle real32, _node_angle_4_.fme_arc_angle real32, _node_angle_5_.fme_arc_angle real32, bu_patch_id int32, centr_x int32, centr_y int32, orient_bb_a int32, orient_bb_b int32
Note: gives us number of edges
TopologyBuilder_Edge: Inspector [off]
LengthCalculator_2
    LEN_ATTR = _length_edge
    MULT = 1
    DIM = 2
    -> File100 (writer CSV2_1)
Note: angles at road intersections
File100 (writer CSV2_1)
    attributes: BU_AREA_BUF real32, OBJECTID string, PERMANENT_IDENTIFIER string, SHAPE_Length real32, _length_orig real32, _length_edge real32, bu_patch_id int32, centr_x int32, centr_y int32, orient_bb_a int32, orient_bb_b int32
Chopper_2
    MAX_VERTICES = 2
    REMNANT_ATTR = _remnant
    MODE = By Vertex
    CHOPPED_ATTR = _chopped
    -> LengthCalculator_3
LengthCalculator_3
    LEN_ATTR = _length_segment
    MULT = 1
    DIM = 2
    -> AzimuthCalculator [LINE]
AzimuthCalculator
    ACANGLE = @Value(acAngle)
    AZIMUTH -> AzimuthCalculator_AZIMUTH
    AZIMUTH -> File10000 (writer CSV2_1)
Note: angles at road vertices
File10000 (writer CSV2_1)
    attributes: BU_AREA_BUF real32, OBJECTID string, PERMANENT_IDENTIFIER string, acAngle real32, _angle real32, _azimuth real32, _length_segment real32, bu_patch_id int32, centr_x int32, centr_y int32, orient_bb_a int32, orient_bb_b int32
AzimuthCalculator_AZIMUTH: Inspector [off]
Tester_Passed: Inspector [off]

FME custom transformer LoopFilter
Tests whether a line is a loop, i.e. whether its end matches the beginning.
The transformers outputs loops through PASSED port, and non-loops through FAILED port.
The isLoop attribute added to each feature. 1 means the feature is loop, and zero means it is not.

Note: LoopFilter / Dmitri Bagh / July 11, 2005
LINE (input)
    -> LineFilter
LineFilter: GeometryFilter
    POINT -> NON-LINEAR (output)
    LINE -> LoopTester
    ARC -> NON-LINEAR (output)
    AREA -> NON-LINEAR (output)
    ELLIPSE -> NON-LINEAR (output)
    TEXT -> NON-LINEAR (output)
    NULL -> NON-LINEAR (output)
Note: LoopTester [ExpressionEvaluator] / _isLoop = (@Coordinate(x,0)-@Coordinate(x,-1))||(@Coordinate(y,0)-@Coordinate(y,-1))
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester] / Test Description: <not set> / TEST @Value(_isLoop) = 0 / Condition: OR / Composite Test Expression: <not set>
TESTER: Tester
    TEST_CLAUSE = TEST @Value(_isLoop) = 0
    BOOL_OP = OR
    TEST_LIST = &_isLoop,=,0
    TEST_MODE = Automatic
    PASSED -> PASSED (output)
    FAILED -> FAILED (output)
PASSED (output)
FAILED (output)
NON-LINEAR (output)
ClosedCurveFilter
    CHECK_NODE_ELEVATION = Yes

FME custom transformer AzimuthCalculator
Calculates the angle and the azimuth of a line or a polyline.
An Azimuth value can range from -180 to 180 With North as zero, South as -180, East as 90 and West as -90. 
Angles increase counterclockwise from the reference point of East (which represents zero degrees).
For polylines it returns the angle and azimuth of a line connecting the first and the last verteices of the polyline. 
The resultant lines have two new attributes - acAngle and acAzimuth.
For getting information about each segment of the polyline use PolylineAnalyzer.
This transformer uses an embedded version of " LoopFilter " custom transformer.

Parameters:
- ACANGLE = @Value(acAngle)   # acAngle

Note: Azimuth Calculator / - Dean Hintz June 13 2005 / - Dmitri Bagh June 30 2005 (minor edits)
LINE (input)
    -> GeometryFilter
Note: Removes all intermediate attributes
ATTRIBUTEREMOVER: AttributeRemover
    REMOVE_ATTRS = acX1,acX2,acZ1,acZ2,_PolylineLoop,_isLoop,_coordcount,acY2,acY1
    -> AZIMUTH (output)
AZIMUTH (output)

Bookmark: Input Filter
  Sorts out all unsuitable features - non linear, and loops.
Note: passes only lines to the next transfomer
GeometryFilter
    BREAK_AGG = No
    GEOM_PORT_NAMES = Line
    LINE -> LoopFilter [LINE]
    <UNFILTERED> -> Not_Line (output)
Note: tests whether a line is a loop
LoopFilter
    PASSED -> LOGGER_2
    FAILED -> COORDINATEFETCHER
LOGGER_2: Logger
    MAXCOORDS = 3
    MESSAGE = Feature is a loop
    MAXFEATS = 20
Not_Line (output)

Bookmark: Angle Calculations
COORDINATEFETCHER: CoordinateFetcher
    X_ATTR = acX1
    Z_DEFAULT = -9999
    Y_ATTR = acY1
    Z_ATTR = acZ1
    IND = 0
    -> COORDINATEFETCHER_2
COORDINATEFETCHER_2: CoordinateFetcher
    X_ATTR = acX2
    Z_DEFAULT = -9999
    Y_ATTR = acY2
    Z_ATTR = acZ2
    IND = -1
    -> EXPRESSIONEVALUATOR_2
EXPRESSIONEVALUATOR_2: ExpressionEvaluator
    VAL_ATTR = _angle
    EXPRESSION = acos((@Value(acX2)-@Value(acX1))/sqrt(pow((@Value(acY2)-@Value(acY1)),2) + pow((@Value(acX2)-@Value(acX1)),2)))* (180/3.1415926535897932)
    -> EXPRESSIONEVALUATOR_6
EXPRESSIONEVALUATOR_6: ExpressionEvaluator
    VAL_ATTR = _angle
    EXPRESSION = ((@Value(acY2)-@Value(acY1))<0)?(360-@Value(_angle)):(@Value(_angle))
    -> TESTER

Bookmark: Azimuth Calculations
  Testers check quadrand, and calculate the Azimuth Accordingly
TESTER: Tester
    TEST_CLAUSE = TEST "@Value(_angle)" > "90"
    BOOL_OP = OR
    TEST_LIST = &acAngle,>,90
    TEST_DESCRIPTION = ""
    TEST_MODE = Automatic
    PASSED -> TESTER_2
    FAILED -> EXPRESSIONEVALUATOR_3
TESTER_2: Tester
    TEST_CLAUSE = TEST "@Value(_angle)" > "270"
    BOOL_OP = OR
    TEST_LIST = &acAngle,""">""",270
    TEST_DESCRIPTION = ""
    TEST_MODE = Automatic
    PASSED -> EXPRESSIONEVALUATOR_5
    FAILED -> EXPRESSIONEVALUATOR_3
EXPRESSIONEVALUATOR_5: ExpressionEvaluator
    VAL_ATTR = _azimuth
    EXPRESSION = 450 - @Value(_angle)
    -> ATTRIBUTEREMOVER
EXPRESSIONEVALUATOR_3: ExpressionEvaluator
    VAL_ATTR = _azimuth
    EXPRESSION = 90 - @Value(_angle)
    -> ATTRIBUTEREMOVER

FME custom transformer LoopFilter_2
Tests whether a line is a loop, i.e. whether its end matches the beginning.
The transformers outputs loops through PASSED port, and non-loops through FAILED port.
An isLoop attribute is added to each feature. 1 means the feature is loop, and zero means it is not.

LINE (input)
    -> LineFilter
Note: LoopFilter / Dmitri Bagh / July 11, 2005
LineFilter: GeometryFilter
    POINT -> NON-LINEAR (output)
    LINE -> LoopTester
    ARC -> NON-LINEAR (output)
    AREA -> NON-LINEAR (output)
    ELLIPSE -> NON-LINEAR (output)
    TEXT -> NON-LINEAR (output)
    NULL -> NON-LINEAR (output)
Note: LoopTester [ExpressionEvaluator:1] / _isLoop = (@Coordinate(x,0)-@Coordinate(x,-1))||(@Coordinate(y,0)-@Coordinate(y,-1)) / Version: 1
Note: Evaluates to 0 if feature is loop, and 1, if it is not.
LoopTester: ExpressionEvaluator
    VAL_ATTR = _isLoop
    EXPRESSION = (@Coordinate(x,0)-@Coordinate(x,-1))||(@Coordinate(y,0)-@Coordinate(y,-1))
    -> TESTER
Note: TESTER [Tester:1] / Test Description: <not set> / TEST &_isLoop = 0 / Condition: OR / Composite Test Expression: <not set> / Version: 1
TESTER: Tester
    TEST_CLAUSE = TEST &_isLoop = 0
    BOOL_OP = OR
    TEST_LIST = &_isLoop,=,0
    TEST_MODE = Automatic
    PASSED -> PASSED (output)
    FAILED -> FAILED (output)
PASSED (output)
FAILED (output)
NON-LINEAR (output)
